FME workspace tiff_shapefile_geodatabase_file2geodatabase_file.fmw

Parameters:
- SourceDataset_TIFF = ""$(FME_MF_DIR)ras250_gb\ras250_gb\data\HP.tif" "$(FME_MF_DIR)ras250_gb\ras250_gb\data\HT.tif" "$(FME_MF_DIR)ras250_gb\ras250_gb\data\HU.tif" "$(FME_MF_DIR)ras250_gb\ras250_gb\data\HW.tif" "$(FME_MF_DIR)ras250_gb\ras250_gb\data\HX.tif" "$(FME_MF_DIR)ras250_gb\ras250_gb\data\HY.tif" "$(FME_MF_DIR)ras250_gb\ras250_gb\data\HZ.tif" "$(FME_MF_DIR)ras250_gb\ras250_gb\data\NA.tif" "$(FME_MF_DIR)ras250_gb\ras250_gb\data\NB.tif" "$(FME_MF_DIR)ras250_gb\ras250_gb\data\NC.tif" "$(FME_MF_DIR)ras250_gb\ras250_gb\data\ND.tif" "$(FME_MF_DIR)ras250_gb\ras250_gb\data\NF.tif" "$(FME_MF_DIR)ras250_gb\ras250_gb\data\NG.tif" "$(FME_MF_DIR)ras250_gb\ras250_gb\data\NH.tif" "$(FME_MF_DIR)ras250_gb\ras250_gb\data\NJ.tif" "$(FME_MF_DIR)ras250_gb\ras250_gb\data\NK.tif" "$(FME_MF_DIR)ras250_gb\ras250_gb\data\NL.tif" "$(FME_MF_DIR)ras250_gb\ras250_gb\data\NM.tif" "$(FME_MF_DIR)ras250_gb\ras250_gb\data\NN.tif" "$(FME_MF_DIR)ras250_gb\ras250_gb\data\NO.tif" "$(FME_MF_DIR)ras250_gb\ras250_gb\data\NR.tif" "$(FME_MF_DIR)ras250_gb\ras250_gb\data\NS.tif" "$(FME_MF_DIR)ras250_gb\ras250_gb\data\NT.tif" "$(FME_MF_DIR)ras250_gb\ras250_gb\data\NU.tif" "$(FME_MF_DIR)ras250_gb\ras250_gb\data\NW.tif" "$(FME_MF_DIR)ras250_gb\ras250_gb\data\NX.tif" "$(FME_MF_DIR)ras250_gb\ras250_gb\data\NY.tif" "$(FME_MF_DIR)ras250_gb\ras250_gb\data\NZ.tif" "$(FME_MF_DIR)ras250_gb\ras250_gb\data\OV.tif" "$(FME_MF_DIR)ras250_gb\ras250_gb\data\SC.tif" "$(FME_MF_DIR)ras250_gb\ras250_gb\data\SD.tif" "$(FME_MF_DIR)ras250_gb\ras250_gb\data\SE.tif" "$(FME_MF_DIR)ras250_gb\ras250_gb\data\SH.tif" "$(FME_MF_DIR)ras250_gb\ras250_gb\data\SJ.tif" "$(FME_MF_DIR)ras250_gb\ras250_gb\data\SK.tif" "$(FME_MF_DIR)ras250_gb\ras250_gb\data\SM.tif" "$(FME_MF_DIR)ras250_gb\ras250_gb\data\SN.tif" "$(FME_MF_DIR)ras250_gb\ras250_gb\data\SO.tif" "$(FME_MF_DIR)ras250_gb\ras250_gb\data\SP.tif" "$(FME_MF_DIR)ras250_gb\ras250_gb\data\SR.tif" "$(FME_MF_DIR)ras250_gb\ras250_gb\data\SS.tif" "$(FME_MF_DIR)ras250_gb\ras250_gb\data\ST.tif" "$(FME_MF_DIR)ras250_gb\ras250_gb\data\SU.tif" "$(FME_MF_DIR)ras250_gb\ras250_gb\data\SV.tif" "$(FME_MF_DIR)ras250_gb\ras250_gb\data\SW.tif" "$(FME_MF_DIR)ras250_gb\ras250_gb\data\SX.tif" "$(FME_MF_DIR)ras250_gb\ras250_gb\data\SY.tif" "$(FME_MF_DIR)ras250_gb\ras250_gb\data\SZ.tif" "$(FME_MF_DIR)ras250_gb\ras250_gb\data\TA.tif" "$(FME_MF_DIR)ras250_gb\ras250_gb\data\TF.tif" "$(FME_MF_DIR)ras250_gb\ras250_gb\data\TG.tif" "$(FME_MF_DIR)ras250_gb\ras250_gb\data\TL.tif" "$(FME_MF_DIR)ras250_gb\ras250_gb\data\TM.tif" "$(FME_MF_DIR)ras250_gb\ras250_gb\data\TQ.tif" "$(FME_MF_DIR)ras250_gb\ras250_gb\data\TR.tif" "$(FME_MF_DIR)ras250_gb\ras250_gb\data\TV.tif""   # Source TIFF (Tagged Image File Format) File(s)
- FEATURE_TYPES =
- DestDataset_GEODATABASE_FILE = $(FME_MF_DIR)ras250_gb\gdb.gdb   # File Geodatabase
- SourceDataset_SHAPEFILE = $(FME_MF_DIR)Data\GB\scotland_and_wales_const_region.shp   # Source Esri Shapefile(s)
- SourceDataset_GEODATABASE_FILE_4 = $(FME_MF_DIR)ras250_gb\gdb.gdb   # File Geodatabase
- SourceDataset_GEODATABASE_FILE = $(FME_MF_DIR)ras250_gb\gdb.gdb   # File Geodatabase
- DestDataset_TIFF = tif_test   # Destination TIFF (Tagged Image File Format) Folder
- DestDataset_POSTGIS_RASTER = db2   # Connection

Readers:
- TIFF_1: TIFF from $(SourceDataset_TIFF)
- SHAPEFILE_1: SHAPEFILE from $(SourceDataset_SHAPEFILE)
- GEODATABASE_FILE_2: GEODATABASE_FILE from $(SourceDataset_GEODATABASE_FILE)
- GEODATABASE_FILE_3: GEODATABASE_FILE from $(SourceDataset_GEODATABASE_FILE_4)

Writers:
- GEODATABASE_FILE_1: GEODATABASE_FILE to $(DestDataset_GEODATABASE_FILE)
- TIFF_2: TIFF to $(DestDataset_TIFF)
- POSTGIS_RASTER_1: POSTGIS_RASTER to $(DestDataset_POSTGIS_RASTER)

scotland_and_wales_const_region (reader SHAPEFILE_1)
    attributes: NAME varchar(100), AREA_CODE varchar(3), DESCRIPTIO varchar(50), FILE_NAME varchar(100), NUMBER number(11,0), NUMBER0 number(11,0), POLYGON_ID number(11,0), UNIT_ID number(11,0), CODE varchar(9), HECTARES float, AREA float, TYPE_CODE varchar(2), DESCRIPT0 varchar(25), TYPE_COD0 varchar(3), DESCRIPT1 varchar(36)
    -> Tester
Tester
    BOOL_OP = AND
    TEST_CLAUSE:
      CASE_INSENSITIVE_TEST @Value(FILE_NAME) CONTAINS south
      CASE_INSENSITIVE_TEST @Value(FILE_NAME) CONTAINS wales
    TEST_MODE = CASE_INSENSITIVE_TEST
    PASSED -> Reprojector_2
Reprojector_2
    DEST = LL-WGS84
    INTERPOLATION_TYPE = NearestNeighbor
    RASTER_CELL_SIZE = PreserveCells
    RASTER_TOLERANCE = 0.0
    REPROJECTED -> SpatialFilter [Filter]
TIFF (reader TIFF_1)
    -> Reprojector
Reprojector
    DEST = LL-WGS84
    INTERPOLATION_TYPE = NearestNeighbor
    RASTER_CELL_SIZE = PreserveCells
    RASTER_TOLERANCE = 0.0
    REPROJECTED -> RasterPropertyExtractor
    REPROJECTED -> Clipper [CANDIDATE]
RasterPropertyExtractor
    -> 2DBoxReplacer
2DBoxReplacer
    MAXXVALATTR = @Value(_max_x)
    MAXYVALATTR = @Value(_max_y)
    MINXVALATTR = @Value(_min_x)
    MINYVALATTR = @Value(_min_y)
    BOX -> AttributeCreator
AttributeCreator
    ATTR_TABLE = SET_TO NewName (varchar(200)) = @Value(fme_basename)_"_"@Value(_num_columns)"x"@Value(_num_rows)
    INPUT_PORT_CONNECTED = CONNECTED
    -> extent (writer GEODATABASE_FILE_1)
extent (writer GEODATABASE_FILE_1)
    attributes: NewName char(200), _num_bands double, _num_rows double, _num_columns double, _spacing_x double, _spacing_y double, _origin_x double, _origin_y double, _rotation_x double, _rotation_y double, _min_x double, _min_y double, _max_x double, _max_y double, _cell_origin_x double, _cell_origin_y double, _upper_left_x double, _upper_left_y double, _upper_right_x double, _upper_right_y double, _lower_right_x double, _lower_right_y double, _lower_left_x double, _lower_left_y double
extent (reader GEODATABASE_FILE_3)
    attributes: OBJECTID integer, NewName char(200), _num_bands double, _num_rows double, _num_columns double, _spacing_x double, _spacing_y double, _origin_x double, _origin_y double, _rotation_x double, _rotation_y double, _min_x double, _min_y double, _max_x double, _max_y double, _cell_origin_x double, _cell_origin_y double, _upper_left_x double, _upper_left_y double, _upper_right_x double, _upper_right_y double, _lower_right_x double, _lower_right_y double, _lower_left_x double, _lower_left_y double, SHAPE_Length double, SHAPE_Area double
    -> SpatialFilter [Candidate]
SpatialFilter
    AGGREGATE_HANDLING = Yes
    BASE_TYPE = Multiple Filters
    CURVE_BOUNDARY_RULE_PARAM = Default Rule
    PASS_CRITERIA = Pass Against One Filter
    PREDATTR = _predicate
    PREDICATES = INTERSECTS
    USE_BOUNDING_BOX = No
    PASSED -> Clipper [CLIPPER]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterPaletteRemover
RasterPaletteRemover
    -> exports (writer POSTGIS_RASTER_1)
exports (writer POSTGIS_RASTER_1)
    attributes: _clipped char(3)
Raster1 (writer TIFF_2)
