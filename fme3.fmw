FME workspace fme3.fmw

Parameters:
- SourceDataset_SHAPEFILE = ""C:\Users\Tomasz\Downloads\T2019_KAR_GERMANY\T2019_KAR_GERMANY\T2019_KAR_POI_TABLE.shp" "C:\Users\Tomasz\Downloads\T2019_KAR_GERMANY\T2019_KAR_GERMANY\T2019_KAR_STREET_NODE.shp" "C:\Users\Tomasz\Downloads\T2019_KAR_GERMANY\T2019_KAR_GERMANY\T2019_KAR_STREETS.shp""   # Source Esri Shapefile(s)
- SourceDataset_CSV2 = C:\Users\Tomasz\Downloads\input.csv   # Source CSV (Comma Separated Value) File(s)
- DestDataset_GEOJSON = $(FME_MF_DIR)geojson.json   # Destination GeoJSON File
- DestDataset_GEODATABASE_FILE = $(FME_MF_DIR)folder.gdb   # File Geodatabase

Readers:
- SHAPEFILE_1: SHAPEFILE from $(SourceDataset_SHAPEFILE)
- CSV2_1: CSV2 from $(SourceDataset_CSV2)

Writers:
- GEOJSON_1: GEOJSON to $(DestDataset_GEOJSON)
- GEODATABASE_FILE_1: GEODATABASE_FILE to $(DestDataset_GEODATABASE_FILE)

T2019_KAR_POI_TABLE (reader SHAPEFILE_1)
    attributes: POI_ID long, LINK_ID long, TYPE varchar(250), POI_NAME varchar(250), ST_NAME varchar(250), LAT number(31,15), LON number(31,15)
    -> Reprojector_4
Reprojector_4
    DEST = DHDN.Berlin/Cassini
    INTERPOLATION_TYPE = NearestNeighbor
    RASTER_CELL_SIZE = PreserveCells
    RASTER_TOLERANCE = 0.0
    REPROJECTED -> SpatialFilter [Candidate]
T2019_KAR_STREET_NODE (reader SHAPEFILE_1)
    attributes: NODE_ID long, LINK_ID long, POINT_NUM long, Z_LEVEL long, INTERSECT varchar(1), LAT number(31,15), LON number(31,15)
    -> Reprojector_2
Reprojector_2
    DEST = DHDN.Berlin/Cassini
    INTERPOLATION_TYPE = NearestNeighbor
    RASTER_CELL_SIZE = PreserveCells
    RASTER_TOLERANCE = 0.0
    REPROJECTED -> intersect [Candidate]
T2019_KAR_STREETS (reader SHAPEFILE_1)
    attributes: LINK_ID long, ST_NAME varchar(254), REF_IN_ID long, NREF_IN_ID long, FUNC_CLASS varchar(1), SPEED_CAT varchar(1), FR_SPEED_L long, TO_SPEED_L long, DIR_TRAVEL varchar(1)
    -> Reprojector_3
Reprojector_3
    DEST = DHDN.Berlin/Cassini
    INTERPOLATION_TYPE = NearestNeighbor
    RASTER_CELL_SIZE = PreserveCells
    RASTER_TOLERANCE = 0.0
    REPROJECTED -> ShortestPathFinder [NETWORK]
    REPROJECTED -> Tester
Tester
    BOOL_OP = OR
    TEST_CLAUSE:
      TEST @Value(DIR_TRAVEL) = B
      TEST @Value(DIR_TRAVEL) = F
    TEST_MODE = TEST
    PASSED -> AttributeCreator_3
    FAILED -> AttributeCreator_4
AttributeCreator_3
    ATTR_TABLE:
      SET_TO DIR_TRAVEL (varchar(1))
      SET_TO FR_SPEED_L (int32)
      SET_TO FUNC_CLASS (varchar(1))
      SET_TO LINK_ID (int32)
      SET_TO NREF_IN_ID (int32)
      SET_TO REF_IN_ID (int32)
      SET_TO SPEED_CAT (varchar(1))
      SET_TO ST_NAME (varchar(254))
      SET_TO TO_SPEED_L (int32)
      SET_TO forward_cost (real32) = @Evaluate(1*@Length())
      SET_TO reverse_cost (real32) = @Evaluate(1*@Length())
    INPUT_PORT_CONNECTED = CONNECTED
    -> ShortestPathFinder_2 [NETWORK]
AttributeCreator_4
    ATTR_TABLE:
      SET_TO DIR_TRAVEL (varchar(1))
      SET_TO FR_SPEED_L (int32)
      SET_TO FUNC_CLASS (varchar(1))
      SET_TO LINK_ID (int32)
      SET_TO NREF_IN_ID (int32)
      SET_TO REF_IN_ID (int32)
      SET_TO SPEED_CAT (varchar(1))
      SET_TO ST_NAME (varchar(254))
      SET_TO TO_SPEED_L (int32)
      SET_TO forward_cost (real32) = @Evaluate(1*@Length())
      SET_TO reverse_cost (real32) = @Evaluate(9999*@Length())
    INPUT_PORT_CONNECTED = CONNECTED
    -> ShortestPathFinder_2 [NETWORK]
CSV (reader CSV2_1)
    attributes: id uint32, x real32, y real64
    -> VertexCreator
VertexCreator
    COORDSYS = LL-WGS84
    MEASURE_TYPE_LOOKUP = CONTINUOUS
    MODE = REPLACE
    REMOVE_ATTRIBUTES = No
    XVAL = @Value(x)
    YVAL = @Value(y)
    MEASURE_TYPE = Continuous
    MODE_NAME = Replace with Point
    -> LineBuilder
LineBuilder
    ACCUM_INPUT_ATTRS_LOOKUP = One
    REMOVE_DUPLICATES_LOOKUP = NO
    ACCUM_INPUT_ATTRS = Use Attributes From One Feature
    REMOVE_DUPLICATES = No
    LINE -> Reprojector
Reprojector
    DEST = DHDN.Berlin/Cassini
    INTERPOLATION_TYPE = NearestNeighbor
    RASTER_CELL_SIZE = PreserveCells
    RASTER_TOLERANCE = 0.0
    REPROJECTED -> ShortestPathFinder [FROM-TO]
    REPROJECTED -> ShortestPathFinder_2 [FROM-TO]
ShortestPathFinder_2
    ALLOW_UTURNS = Yes
    REORDER_MODE = NONE
    SNAP_POINTS = Yes
    SNAP_TOLERANCE = 200
    THREE_D = No
    WEIGHT_ATTR_1 = @Value(forward_cost)
    WEIGHT_ATTR_2 = @Value(reverse_cost)
    WEIGHT_ATTR_CHOICE = BY_TWO_ATTRIBUTES
    PATH -> Bufferer
    PATH -> intersect [Filter]
    PATH -> AttributeCreator
    PATH -> FeatureClass1 (writer GEODATABASE_FILE_1)
Bufferer
    ANGLE = 22.5
    CAP_STYLE_LOOKUP = CAP_ARC
    CORNER_STYLE_LOOKUP = JOIN_ARC
    MODE = AREA
    OFFSET = 5
    OFFSET_UNITS = METERS
    PRECISION = APPROX
    CAP_STYLE = Arc
    CORNER_STYLE = Arc
    BUFFERED -> SpatialFilter [Filter]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> NewFeatureType (writer GEOJSON_1)
NewFeatureType (writer GEOJSON_1)
    attributes: id int, x float, y float, _total_cost string, POI_ID int, LINK_ID int, TYPE string, POI_NAME string, ST_NAME string, LAT string, LON string, _predicate string
intersect: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator
StatisticsCalculator
    ATTR_ACCUM_MODE = None
    CALCULATION_MODE = NUMERIC
    FEAT_STATS = id,NUMERIC_MODE,,,COUNT,,,,,,,,,,
    SUMMARY -> FeatureClass1 (writer GEODATABASE_FILE_1)
AttributeCreator
    ATTR_TABLE = SET_TO road_length (real32) = @Value(_total_cost)
    INPUT_PORT_CONNECTED = CONNECTED
    -> FeatureClass1 (writer GEODATABASE_FILE_1)
FeatureClass1 (writer GEODATABASE_FILE_1)
    attributes: id_total_count bigint, road_length float, id double, x float, y double, _total_cost char(2048)
ShortestPathFinder
    ALLOW_UTURNS = Yes
    REORDER_MODE = NONE
    SNAP_POINTS = Yes
    SNAP_TOLERANCE = 200
    THREE_D = No
    WEIGHT_ATTR_CHOICE = BY_LENGTH
    PATH -> Inspector
Inspector
